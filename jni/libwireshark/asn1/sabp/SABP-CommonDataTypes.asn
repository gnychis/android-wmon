-- SABP-CommonDataTypes.asn
--
-- Taken from 3GPP TS 25.419 V9.0.0 (2009-12)
-- http://www.3gpp.org/ftp/Specs/archive/25_series/25.419/25419-700.zip/25419-700.DOC
--
-- 9.3.5	Common Definitions
--
-- $Id: SABP-CommonDataTypes.asn 31356 2009-12-23 14:06:57Z etxrab $
--

-- **************************************************************
--
-- Common definitions
--
-- **************************************************************

SABP-CommonDataTypes {
itu-t (0) identified-organization (4) etsi (0) mobileDomain (0) 
umts-Access (20) modules (3) sabp (3) version1 (1) sabp-CommonDataTypes (3) } 

DEFINITIONS AUTOMATIC TAGS ::= 

BEGIN

Criticality		::= ENUMERATED { reject, ignore, notify }

Presence		::= ENUMERATED { optional, conditional, mandatory }

ProcedureCode		::= INTEGER (0..255)

ProtocolExtensionID	::= INTEGER (0..65535)

ProtocolIE-ID		::= INTEGER (0..65535)

TriggeringMessage		::= ENUMERATED {initiating-message, successful-outcome, unsuccessful-outcome, outcome}

END
