-- $Id: PCAP-Constants.asn 34929 2010-11-17 16:23:10Z etxrab $
--
-- 3GPP TS 25.453 V9.1.0 (2010-03)
--
-- 9.3.6	Constant Definitions
-- **************************************************************
--
-- Constant definitions
--
-- **************************************************************

PCAP-Constants { 
itu-t (0) identified-organization (4) etsi (0) mobileDomain (0) 
umts-Access (20) modules (3) pcap(4) version1 (1) pcap-Constants (4) } 

DEFINITIONS AUTOMATIC TAGS ::= 

BEGIN

IMPORTS
	ProcedureCode,
	ProtocolIE-ID
FROM PCAP-CommonDataTypes;


-- **************************************************************
--
-- Elementary Procedures
--
-- **************************************************************

id-PositionCalculation				ProcedureCode ::= 1
id-InformationExchangeInitiation	ProcedureCode ::= 2
id-InformationReporting				ProcedureCode ::= 3
id-InformationExchangeTermination	ProcedureCode ::= 4
id-InformationExchangeFailure		ProcedureCode ::= 5
id-ErrorIndication					ProcedureCode ::= 6
id-privateMessage					ProcedureCode ::= 7
id-PositionParameterModification	ProcedureCode ::= 8
id-PositionInitiation				ProcedureCode ::= 9
id-PositionActivation				ProcedureCode ::= 10
id-Abort							ProcedureCode ::= 11
id-PositionPeriodicReport			ProcedureCode ::= 12
id-PositionPeriodicResult			ProcedureCode ::= 13
id-PositionPeriodicTermination		ProcedureCode ::= 14


-- **************************************************************
--
-- Lists
--
-- **************************************************************

maxNrOfErrors						INTEGER ::= 256
maxSat								INTEGER ::= 16
maxSatAlmanac						INTEGER ::= 32
maxNrOfLevels						INTEGER ::= 256
maxNrOfPoints						INTEGER ::= 15
maxNrOfExpInfo						INTEGER ::= 32
maxNrOfMeasNCell					INTEGER ::= 32
maxNrOfMeasurements					INTEGER ::= 16
maxNrOfSets							INTEGER ::= 3
maxRateMatching						INTEGER ::= 256
maxNrOfTFs							INTEGER ::= 32
maxTTI-count						INTEGER ::= 4
maxTS-1								INTEGER ::= 13 
maxCCTrCH							INTEGER ::= 8
maxTF								INTEGER ::= 32
maxTFC								INTEGER ::= 1024
maxPRACH							INTEGER ::= 16
maxTrCH								INTEGER ::= 32
maxTGPS								INTEGER ::= 6
maxNoOfMeasurements					INTEGER ::= 16
maxCellMeas							INTEGER ::= 32
maxNrOfEDPCCH-PO-QUANTSTEPs			INTEGER ::= 8	-- FFS
maxNrOfRefETFCI-PO-QUANTSTEPs		INTEGER ::= 8	-- FFS
maxNrOfRefETFCIs					INTEGER ::= 8
maxSet								INTEGER ::= 9
maxGANSSSat							INTEGER ::= 64
maxSgnType							INTEGER ::= 8
maxGANSS							INTEGER ::= 8
maxGANSSSet							INTEGER ::= 9
maxGANSSSatAlmanac					INTEGER ::= 36
maxGANSSClockMod					INTEGER ::= 4
maxGANSS-1							INTEGER ::= 7


-- **************************************************************
--
-- IEs
--
-- **************************************************************

id-Cause										ProtocolIE-ID ::= 1
id-CriticalityDiagnostics						ProtocolIE-ID ::= 2
id-GPS-UTRAN-TRU								ProtocolIE-ID ::= 3
id-InformationExchangeID						ProtocolIE-ID ::= 4
id-InformationExchangeObjectType-InfEx-Rprt		ProtocolIE-ID ::= 5
id-InformationExchangeObjectType-InfEx-Rqst		ProtocolIE-ID ::= 6
id-InformationExchangeObjectType-InfEx-Rsp		ProtocolIE-ID ::= 7
id-InformationReportCharacteristics				ProtocolIE-ID ::= 8
id-InformationType								ProtocolIE-ID ::= 9
id-GPS-MeasuredResultsList						ProtocolIE-ID ::= 10
id-MethodType									ProtocolIE-ID ::= 11
id-RefPosition-InfEx-Rqst						ProtocolIE-ID ::= 12
id-RefPosition-InfEx-Rsp						ProtocolIE-ID ::= 13
id-RefPosition-Inf-Rprt							ProtocolIE-ID ::= 14
id-RequestedDataValue							ProtocolIE-ID ::= 15
id-RequestedDataValueInformation				ProtocolIE-ID ::= 16
id-TransactionID								ProtocolIE-ID ::= 17
id-UE-PositionEstimate							ProtocolIE-ID ::= 18
-- WS extension
id-Unknown-19									ProtocolIE-ID ::= 19
id-CellId-MeasuredResultsSets					ProtocolIE-ID ::= 20
-- WS extension
id-Unknown-21									ProtocolIE-ID ::= 21
id-OTDOA-MeasurementGroup						ProtocolIE-ID ::= 22
id-AccuracyFulfilmentIndicator					ProtocolIE-ID ::= 23
id-HorizontalAccuracyCode						ProtocolIE-ID ::= 24
id-VerticalAccuracyCode							ProtocolIE-ID ::= 25
id-UTDOA-Group									ProtocolIE-ID ::= 26
-- WS extension
id-Unknown-27									ProtocolIE-ID ::= 27
id-RequestType									ProtocolIE-ID ::= 28
id-UE-PositioningCapability						ProtocolIE-ID ::= 29
id-UC-id										ProtocolIE-ID ::= 30
id-ResponseTime									ProtocolIE-ID ::= 31
id-PositioningPriority							ProtocolIE-ID ::= 32
id-ClientType									ProtocolIE-ID ::= 33
id-PositioningMethod							ProtocolIE-ID ::= 34
id-UTDOAPositioning								ProtocolIE-ID ::= 35
id-GPSPositioning								ProtocolIE-ID ::= 36
id-OTDOAAssistanceData							ProtocolIE-ID ::= 37
id-Positioning-ResponseTime						ProtocolIE-ID ::= 38
id-EnvironmentCharacterisation					ProtocolIE-ID ::= 39
id-PositionData									ProtocolIE-ID ::= 40
id-IncludeVelocity								ProtocolIE-ID ::= 41
id-VelocityEstimate								ProtocolIE-ID ::= 42
id-rxTimingDeviation768Info						ProtocolIE-ID ::= 43
id-UC-ID-InfEx-Rqst								ProtocolIE-ID ::= 44
id-UE-PositionEstimateInfo						ProtocolIE-ID ::= 45
id-UTRAN-GPSReferenceTime						ProtocolIE-ID ::= 46
id-UTRAN-GPSReferenceTimeResult					ProtocolIE-ID ::= 47
id-UTRAN-GPS-DriftRate							ProtocolIE-ID ::= 48
id-OTDOA-AddMeasuredResultsInfo					ProtocolIE-ID ::= 49
id-GPS-ReferenceLocation						ProtocolIE-ID ::= 50
id-OTDOA-MeasuredResultsSets					ProtocolIE-ID ::= 51
-- WS extension
id-Unknown-52									ProtocolIE-ID ::= 52
id-Unknown-53									ProtocolIE-ID ::= 53
id-Unknown-54									ProtocolIE-ID ::= 54
id-rxTimingDeviation384extInfo					ProtocolIE-ID ::= 55
id-ExtendedRoundTripTime						ProtocolIE-ID ::= 56
id-PeriodicPosCalcInfo							ProtocolIE-ID ::= 57
id-PeriodicLocationInfo							ProtocolIE-ID ::= 58
id-AmountOfReporting							ProtocolIE-ID ::= 59
id-MeasInstructionsUsed							ProtocolIE-ID ::= 60
id-RRCstateChange								ProtocolIE-ID ::= 61
id-PeriodicTerminationCause						ProtocolIE-ID ::= 62
id-MeasurementValidity							ProtocolIE-ID ::= 63
id-roundTripTimeInfoWithType1					ProtocolIE-ID ::= 64
-- WS extension
id-Unknown-65									ProtocolIE-ID ::= 65
id-CellIDPositioning							ProtocolIE-ID ::= 66
id-AddMeasurementInfo							ProtocolIE-ID ::= 67
id-Extended-RNC-ID								ProtocolIE-ID ::= 68
id-GANSS-CommonAssistanceData					ProtocolIE-ID ::= 69
id-GANSS-GenericAssistanceDataList				ProtocolIE-ID ::= 70
id-GANSS-MeasuredResultsList					ProtocolIE-ID ::= 71
id-GANSS-UTRAN-TRU								ProtocolIE-ID ::= 72
id-GANSSPositioning								ProtocolIE-ID ::= 73 
id-GANSS-PositioningDataSet						ProtocolIE-ID ::= 74
id-GNSS-PositioningMethod						ProtocolIE-ID ::= 75
id-NetworkAssistedGANSSSuport					ProtocolIE-ID ::= 76
id-TUTRANGANSSMeasurementValueInfo				ProtocolIE-ID ::= 77
id-AdditionalGPSAssistDataRequired				ProtocolIE-ID ::= 78
id-AdditionalGanssAssistDataRequired			ProtocolIE-ID ::= 79
id-angleOfArrivalLCR							ProtocolIE-ID ::= 80
id-extendedTimingAdvanceLCR						ProtocolIE-ID ::= 81
id-additionalMeasurementInforLCR				ProtocolIE-ID ::= 82
id-timingAdvanceLCR-R7							ProtocolIE-ID ::= 83
id-rxTimingDeviationLCR 						ProtocolIE-ID ::= 84
id-GPSReferenceTimeUncertainty					ProtocolIE-ID ::= 85 
id-GANSS-AddIonoModelReq						ProtocolIE-ID ::= 86
id-GANSS-EarthOrientParaReq						ProtocolIE-ID ::= 87
id-GANSS-Additional-Ionospheric-Model			ProtocolIE-ID ::= 88
id-GANSS-Earth-Orientation-Parameters			ProtocolIE-ID ::= 89
id-GANSS-Additional-Time-Models					ProtocolIE-ID ::= 90
id-GANSS-Additional-Navigation-Models			ProtocolIE-ID ::= 91
id-GANSS-Additional-UTC-Models					ProtocolIE-ID ::= 92
id-GANSS-Auxiliary-Information					ProtocolIE-ID ::= 93
id-GANSS-SBAS-ID								ProtocolIE-ID ::= 94
id-GANSS-SBAS-IDs								ProtocolIE-ID ::= 95
id-GANSS-Signal-IDs								ProtocolIE-ID ::= 96
id-supportGANSSNonNativeADchoices				ProtocolIE-ID ::= 97
id-PositionDataUEbased							ProtocolIE-ID ::= 98
id-ganssCodePhaseAmbiguityExt 					ProtocolIE-ID ::= 99
id-ganssIntegerCodePhaseExt						ProtocolIE-ID ::= 100
id-GANSScarrierPhaseRequested					ProtocolIE-ID ::= 101
id-GANSSMultiFreqMeasRequested					ProtocolIE-ID ::= 102
id-ganssReq-AddIonosphericModel					ProtocolIE-ID ::= 103
id-ganssReq-EarthOrientPara						ProtocolIE-ID ::= 104
id-ganssAddNavigationModel-req					ProtocolIE-ID ::= 105
id-ganssAddUTCModel-req							ProtocolIE-ID ::= 106
id-ganssAuxInfo-req								ProtocolIE-ID ::= 107
id-GANSS-AlmanacModelChoice						ProtocolIE-ID ::= 108
id-GANSS-alm-keplerianNAVAlmanac				ProtocolIE-ID ::= 109
id-GANSS-alm-keplerianReducedAlmanac			ProtocolIE-ID ::= 110
id-GANSS-alm-keplerianMidiAlmanac				ProtocolIE-ID ::= 111
id-GANSS-alm-keplerianGLONASS					ProtocolIE-ID ::= 112
id-GANSS-alm-ecefSBASAlmanac					ProtocolIE-ID ::= 113
id-UTRAN-GANSSReferenceTimeResult				ProtocolIE-ID ::= 114
id-GANSS-Reference-Time-Only					ProtocolIE-ID ::= 115
id-GANSS-AddADchoices							ProtocolIE-ID ::= 116 
id-OTDOA-ReferenceCellInfo						ProtocolIE-ID ::= 117 
id-DGNSS-ValidityPeriod							ProtocolIE-ID ::= 118


END
