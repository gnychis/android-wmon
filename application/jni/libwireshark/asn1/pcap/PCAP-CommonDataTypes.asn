-- $Id: PCAP-CommonDataTypes.asn 34929 2010-11-17 16:23:10Z etxrab $
--
-- 3GPP TS 25.453 V9.2.0 (2010-09)
--
--9.3.5	Common Definitions
-- **************************************************************
--
-- Common definitions
--
-- **************************************************************

PCAP-CommonDataTypes {
itu-t (0) identified-organization (4) etsi (0) mobileDomain (0) 
umts-Access (20) modules (3) pcap(4) version1 (1) pcap-CommonDataTypes (3)  }

DEFINITIONS AUTOMATIC TAGS ::= 

BEGIN

-- **************************************************************
--
-- Extension constants
--
-- **************************************************************

maxPrivateIEs 									INTEGER ::= 65535
maxProtocolExtensions							INTEGER ::= 65535
maxProtocolIEs									INTEGER ::= 65535

-- **************************************************************
--
-- Common Data Types
--
-- **************************************************************
Criticality		::= ENUMERATED { reject, ignore, notify }

Presence		::= ENUMERATED { optional, conditional, mandatory }

PrivateIE-ID	::= CHOICE {
	local				INTEGER (0..65535),
	global				OBJECT IDENTIFIER
}


ProcedureCode		::= INTEGER (0..255)


ProtocolIE-ID		::= INTEGER (0..maxProtocolIEs)

TransactionID		::= CHOICE {
	shortTID			INTEGER (0..127),
	longTID				INTEGER (0..32767)
}

TriggeringMessage	::= ENUMERATED { initiating-message, successful-outcome, unsuccessful-outcome, outcome }

END
